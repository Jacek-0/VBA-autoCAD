Attribute VB_Name = "Legend_creation"
Attribute VB_Base = "0{435E89FB-D402-4315-A31D-E624D264C4FA}{91E83F24-20C8-46B6-8A32-71B7FDF5CDE7}"
Attribute VB_GlobalNameSpace = False
Attribute VB_Creatable = False
Attribute VB_PredeclaredId = True
Attribute VB_Exposed = False
Attribute VB_TemplateDerived = False
Attribute VB_Customizable = False
Dim isDragging As Boolean
Dim startIndex As Integer

Private Sub Heading1_Click()

End Sub

Private Sub UserForm_Activate()

Legend_creation_init
End Sub


Private Sub Legend_creation_init()

    Dim lyr As AcadLayer
    Me.ListBoxLayers.Clear

    For Each lyr In ThisDrawing.layers
        Me.ListBoxLayers.AddItem lyr.Name
    Next lyr

    Debug.Print "Rysunek", ThisDrawing.Name
    Debug.Print "Liczba warst:", ThisDrawing.layers.Count
End Sub

    
    Private Sub ListBoxLayers_MouseDown(ByVal Button As Integer, ByVal Shift As Integer, ByVal X As Single, ByVal Y As Single)
        ' Start dragging
        isDragging = True
        startIndex = ListBoxLayers.ListIndex
    End Sub
    
    Private Sub ListBoxLayers_MouseMove(ByVal Button As Integer, ByVal Shift As Integer, ByVal X As Single, ByVal Y As Single)
        If isDragging Then
            Dim currentIndex As Integer
            currentIndex = ListBoxLayers.ListIndex
            
            ' Select range of items
            Dim i As Integer
            For i = 0 To ListBoxLayers.ListCount - 1
                If i >= startIndex And i <= currentIndex Then
                    ListBoxLayers.Selected(i) = True
                ElseIf i >= currentIndex And i <= startIndex Then
                    ListBoxLayers.Selected(i) = True
                Else
                    ListBoxLayers.Selected(i) = False
                End If
            Next i
        End If
    End Sub
    
    Private Sub ListBoxLayers_MouseUp(ByVal Button As Integer, ByVal Shift As Integer, ByVal X As Single, ByVal Y As Single)
        ' Stop dragging
        isDragging = False
    End Sub
Private Sub CreateLegend_btn_Click()
    Dim selectedLayers As New Collection
    Dim i As Integer

    ' Pobiera zaznaczone warstwy
    For i = 0 To Me.ListBoxLayers.ListCount - 1
        If Me.ListBoxLayers.Selected(i) Then
            selectedLayers.Add Me.ListBoxLayers.List(i)
        End If
    Next i

    ' Jeśli nie wybrano żadnej warstwy, wyświetl komunikat i zakończ
    If selectedLayers.Count = 0 Then
        MsgBox "Nie wybrano żadnej warstwy", vbExclamation
        Exit Sub
    End If

    ' Zamykamy formularz
    Unload Me

    ' Tworzymy tabelę po zamknięciu formularza
    CreateLayerLegendTable selectedLayers
End Sub


Private Sub cmdRefreshTable_Click()
    Dim layers As New Collection
    Dim obj As AcadLayer

    ' Pobieramy listę wszystkich warstw w rysunku
    For Each obj In ThisDrawing.layers
        layers.Add obj.Name
    Next obj

    ' Odświeżenie tabeli
    UpdateLayerLegendTable layers
End Sub



Private Sub ListBoxLayers_Click()

End Sub

Attribute VB_Name = "Main"
Public tableObj As AcadTable

Public Sub ShowLayerLegenedForm()

    Legend_creation.show

End Sub
Public Sub CreateLayerLegendTable(ByVal layers As Collection)

    If Not tableObj Is Nothing Then
        UpdateLayerLegendTable layers
        Exit Sub
    End If
    
    
    Dim insertionPoint(0 To 2) As Double
    
    Unload Legend_creation

    ' Pobieramy punkt po zamknięciu formularza
    On Error Resume Next
    Dim pickedPoint As Variant
    pickedPoint = ThisDrawing.Utility.GetPoint(, "Wybierz miejsce na tabelę")
    If Err.Number <> 0 Then
        MsgBox "Nie wybrano punktu. Anulowano operację.", vbExclamation
        Exit Sub
    End If
    On Error GoTo 0
    
    insertionPoint(0) = pickedPoint(0)
    insertionPoint(1) = pickedPoint(1)
    insertionPoint(2) = pickedPoint(2)

    ' Tworzenie tabeli
    Dim numRows As Integer, numCols As Integer
    numRows = layers.Count + 2 '+1 jako nagłówek i 1 na ilosc, dlugosc i nazwe
    numCols = 3 '3 kolumny

    Dim myRowHeight As Double, myColWidth As Double
    myRowHeight = 2
    myColWidth = 50

    Set tableObj = ThisDrawing.ModelSpace.AddTable(insertionPoint, numRows, numCols, myRowHeight, myColWidth)

    ' Nagłówki tabeli
    tableObj.SetText 0, 0, ""
    tableObj.SetText 1, 0, "Nazwa warstwy"
    tableObj.SetText 1, 1, "Długość"
    tableObj.SetText 1, 2, "Ilość"

    UpdateLayerLegendTable layers
End Sub

Public Sub UpdateLayerLegendTable(ByVal layers As Collection)

    If tableObj Is Nothing Then
        MsgBox "Brak istniejącej tabeli do odświeżenia. Stwórz tabelę przed odświeżeniem.", vbExclamation
        Exit Sub
    End If

    Dim i As Integer, layerName As String
    Dim totalLength As Double, objectCount As Long
    Dim obj As AcadEntity

    For i = 1 To layers.Count
        layerName = layers(i)
        totalLength = 0
        objectCount = 0

        'Obliczanie ilości i długości
        For Each obj In ThisDrawing.ModelSpace
            If obj.Layer = layerName Then
                objectCount = objectCount + 1
                If TypeOf obj Is AcadLine Or TypeOf obj Is AcadLWPolyline Then
                    totalLength = totalLength + obj.Length
                End If
            End If
        Next obj

        tableObj.SetText i + 1, 0, layerName
        tableObj.SetText i + 1, 1, Format(totalLength, "0.00")
        tableObj.SetText i + 1, 2, CStr(objectCount)
    Next i

    tableObj.Update
End Sub

Sub StartLegendCreator()

    ShowLayerLegenedForm
End Sub

Attribute VB_Name = "ThisDrawing"
Attribute VB_Base = "0{345D3165-3889-4694-AB75-A91A27B217E8}"
Attribute VB_GlobalNameSpace = False
Attribute VB_Creatable = False
Attribute VB_PredeclaredId = True
Attribute VB_Exposed = True
Attribute VB_TemplateDerived = False
Attribute VB_Customizable = True

Private Sub AcadDocument_BeginSave(ByVal FileName As String)

End Sub
